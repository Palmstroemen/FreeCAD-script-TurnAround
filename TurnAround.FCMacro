# TurnAround
#
# Turns the view by 180 degrees around the axis that appears most vertical on the screen,
# so you look at the backside of your model. If something is selected, all other objects
# are hidden for the turn. The next run turns the view back and shows them again.
# This makes it very easy to select faces, edges and points on the backside of a body.
#
# Usage:
#   Select something (e.g. a face), run the macro, select on the backside,
#   run the macro again. Without a selection the macro only turns the view.
#   It is a real time-saver if you assign a shortcut to it
#   (Tools -> Customize... -> Macros: choose TurnAround.FCMacro, enter a shortcut, Add).
#
# Settings:
#   Rotations: number of runs for a full turn (2 = 180 degrees, 3 = 120 degrees, 4 = 90 degrees).
#              The objects are hidden on the first run and shown again after the last one.
#   Debug:     selects the objects that would stay visible instead of hiding the others.
#
# Changelog:
#   1.0.1 (2026-10-28): hidden members of a group stay hidden when the group is shown again.
#                       The view turns around the selection and comes back exactly to where it was.
#   1.0.0 (2026-10-28): first release. Keeps its state outside the document, keeps the containers
#                       of the selection (Part, Body) and the content of selected containers visible.
#                       Turns around the most vertical axis in every view, also in the top view.

__Name__ = 'TurnAround'
__Comment__ = 'Turns the view to the backside and hides all non-selected objects until you turn back'
__Author__ = 'Palmstroemen'
__Date__ = '2026-10-28'
__Version__ = '1.0.1'
__License__ = 'MIT'
__Web__ = 'https://github.com/Palmstroemen/FreeCAD-script-TurnAround'
__Wiki__ = ''
__Icon__ = 'TurnAroundIcon.png'
__Help__ = 'Select something, run the macro, select on the backside, run it again. Assign a shortcut to it.'
__Status__ = 'Stable'
__Requires__ = 'FreeCAD >= 0.21'
__Communication__ = 'https://github.com/Palmstroemen/FreeCAD-script-TurnAround/issues'
__Files__ = 'TurnAroundIcon.png'

Rotations = 2
Degrees  = 360/Rotations
Debug = False			# shows the Elements in the tree that will be excluded from hiding.


import FreeCAD as App
import FreeCADGui as Gui
from PySide import QtCore
from pivy import coin	# needed for the camera node of the view

TurnMs = 500			# duration of the turn of the view.
DelayMs = 800			# waits for the turn of the view before hiding and showing elements.


def turnStates():
	# The state of a turn in progress (hidden objects, remaining turns, turn center and the camera
	# before the first turn) per document.
	# It is kept in the FreeCAD module and not in the document, so the document stays
	# unchanged and the state survives until the next run of the macro.
	if not hasattr(App, "TurnAroundStates"):
		App.TurnAroundStates = {}
	return App.TurnAroundStates


def findParentsOf(obj):
	# finds all containers (Part, Body, Group ...) that hold the object, at any depth.
	# obj.Parents only follows the containers, not dependencies like Binders or expressions.
	parents = set()
	for top, subname in obj.Parents:
		parents.add(top)
		for name in subname.split(".")[:-2]:	# 'Body.Box.' lists the containers below top, then the object itself
			parent = top.Document.getObject(name)
			if parent:
				parents.add(parent)
	return parents


def findObjectsToKeep(doc, Selection):
	# the selected objects, the containers holding them and the content of selected containers.
	selected_objects = {sel.Object for sel in Selection}
	keep = set(selected_objects)
	for obj in selected_objects:
		keep |= findParentsOf(obj)
	for obj in doc.Objects:
		if findParentsOf(obj) & selected_objects:
			keep.add(obj)
	return keep


def hideNonSelectedObjects(doc):
	# hides all currently visible objects that are neither selected, nor containers of the selection, nor inside a selected container,
	# and returns the names of the hidden objects.

	keep = findObjectsToKeep(doc, Gui.Selection.getSelectionEx(doc.Name))

	if Debug:
		# in Debug-Mode don't hide the untouched objects but select the kept objects instead to check
		# if the parents-finder works well.
		for obj in keep:
			Gui.Selection.addSelection(obj)
		return []

	hidden_objects = [obj for obj in doc.Objects
		if obj.ViewObject and obj.ViewObject.Visibility and obj not in keep]
	for obj in hidden_objects:
		obj.ViewObject.Visibility = False
	return [obj.Name for obj in hidden_objects]


def showNonSelectedObjects(doc, names):
	# shows the hidden objects again. Objects deleted in the meantime are skipped.
	print("Showing again")
	before = {obj.Name: obj.ViewObject.Visibility for obj in doc.Objects if obj.ViewObject}
	for name in names:
		obj = doc.getObject(name)
		if obj and obj.ViewObject:
			obj.ViewObject.Visibility = True

	# showing a group shows all its members, also those that were hidden before. Hide them again.
	for obj in doc.Objects:
		if obj.ViewObject and obj.Name not in names and obj.ViewObject.Visibility != before.get(obj.Name):
			obj.ViewObject.Visibility = before[obj.Name]


def hideAndShow(docName, center, camera):
	# if any elements are selected, this function hides all other objects on the first turn.
	# when after several turns the view rotates back to its original position it shows all hidden objects again.
	# for this it counts the remaining turns to get back to the original position
	# (for a 180° rotation this is 2, for a 120° rotation this should be 3 and for a 90° rotation it should be 4)

	if docName not in App.listDocuments():
		return							# the document has been closed in the meantime
	doc = App.getDocument(docName)
	states = turnStates()
	state = states.get(docName)

	if Gui.Selection.getSelection(docName):
		if state is None:
			# now we are on the first turn and want to hide all other objects.
			print("# first turn, hide objects")
			states[docName] = {"turns": Rotations - 1, "hidden": hideNonSelectedObjects(doc),
				"center": center, "camera": camera}

		else:
			state["turns"] -= 1
			if state["turns"] > 0:
				# here we are on the run. Objects should be hidden by now.
				print("# turning")
			else:
				# we have done a full turn and want to make the hidden objects reappear.
				print("# last turn, show objects")
				state = states.pop(docName)
				showNonSelectedObjects(doc, state["hidden"])
				# back at the start: set the camera exactly as it was, without rounding errors
				Gui.getDocument(docName).ActiveView.setCamera(state["camera"])

	elif state is not None:
		# The Selection got lost. In this case we also want to make all the hidden objects to reappear.
		print("# lost selection, show objects")
		showNonSelectedObjects(doc, states.pop(docName)["hidden"])

	else:
		print("No Selection: If you select anything all other objects will be hidden for one whole turn.")
		print("              After",Rotations-1,"more rotations the hidden objects will reappear again.")
		print("              This makes it very easy to select things on the backside of objects.")


def mostVerticalAxis(cam):
	# finds the model axis (X, Y or Z) that appears most vertical on the screen,
	# pointing upwards, so the turn has the same direction on the screen for every axis.
	up = cam.multVec(App.Vector(0, 1, 0))		# the screen's up direction in model coordinates
	axes = [App.Vector(1, 0, 0), App.Vector(0, 1, 0), App.Vector(0, 0, 1)]
	axis = max(axes, key=lambda a: abs(a.dot(up)))
	return axis if axis.dot(up) > 0 else axis.negative()


def turnCenter(docName, node):
	# the center of the selection, so the selection stays in view.
	# Without a selection the focal point of the camera, which a turn around it does not move.
	box = App.BoundBox()
	for sel in Gui.Selection.getSelectionEx(docName, 0):
		for sub in sel.SubElementNames or [""]:
			try:
				shape = sel.Object.getSubObject(sub)
			except Exception:
				shape = None
			if hasattr(shape, "BoundBox") and shape.BoundBox.isValid():
				box.add(shape.BoundBox)
	if box.isValid():
		return box.Center
	position = App.Vector(*node.position.getValue().getValue())
	direction = App.Rotation(*node.orientation.getValue().getValue()).multVec(App.Vector(0, 0, -1))
	return position + direction * node.focalDistance.getValue()


def turnCamera(node, axis, degrees, center):
	# turns the camera around 'center' in small steps. FreeCAD's setCameraOrientation turns
	# around a rotation center of its own, so the view would not come back to where it was.
	position = App.Vector(*node.position.getValue().getValue())
	orientation = App.Rotation(*node.orientation.getValue().getValue())
	steps = 20

	def step(i):
		t = i / steps
		t = t * t * (3 - 2 * t)				# starts and ends smoothly
		turn = App.Rotation(axis, degrees * t)
		p = center + turn.multVec(position - center)
		q = turn.multiply(orientation).Q
		try:
			node.position.setValue(p.x, p.y, p.z)
			node.orientation.setValue(q[0], q[1], q[2], q[3])
		except Exception:
			return						# the view has been closed in the meantime
		if i < steps:
			QtCore.QTimer.singleShot(TurnMs // steps, lambda: step(i + 1))

	step(1)


# Turns the view by 'Degrees' around the axis that appears most vertical.
if Gui.ActiveDocument is None:
	print("TurnAround: please open a document first.")
else:
	view = Gui.ActiveDocument.ActiveView
	docName = Gui.ActiveDocument.Document.Name
	node = view.getCameraNode()
	state = turnStates().get(docName)
	center = state["center"] if state else turnCenter(docName, node)
	camera = view.getCamera()			# kept by hideAndShow on the first turn
	turnCamera(node, mostVerticalAxis(view.getCameraOrientation()), Degrees, center)

	# Wait a moment after rotation to hide and show elements.
	QtCore.QTimer.singleShot(DelayMs, lambda: hideAndShow(docName, center, camera))
